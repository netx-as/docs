NETX-MIB DEFINITIONS ::= BEGIN

IMPORTS
    OBJECT-TYPE, NOTIFICATION-TYPE, MODULE-IDENTITY, enterprises
	FROM SNMPv2-SMI
    DisplayString
	FROM SNMPv2-TC;

netxMib MODULE-IDENTITY
    LAST-UPDATED "202003220000Z"
    ORGANIZATION "NetX Networks"
    CONTACT-INFO    
	"    postal:   602 00 Brno
                   Czech Republic

         email:    info@netx.as
        "
    DESCRIPTION
	"This module defines MIB for extensions produced by 
	NetX Networks. 

    NetX Networks, info@netx.as "
	::= { enterprises 55203 }

system	OBJECT IDENTIFIER ::= { netxMib 1 }

-- dt 55203.1.1 string /system/platform 
netxPlatform OBJECT-TYPE
    SYNTAX	DisplayString
    MAX-ACCESS	not-accessible
    STATUS	current
    DESCRIPTION
	"The NetX Platform."
    ::= { system 1 }

-- dt 55203.1.2 string /system/serial
netxSerial OBJECT-TYPE
    SYNTAX	DisplayString
    MAX-ACCESS	not-accessible
    STATUS	current
    DESCRIPTION
	"The NetX Serial Number"
    ::= { system 2 }

-- dt 55203.1.3 string /system/netc/version
netcVersion OBJECT-TYPE
    SYNTAX	DisplayString
    MAX-ACCESS	not-accessible
    STATUS	current
    DESCRIPTION
	"The netc Platform."
    ::= { system 3 }

cpu	OBJECT IDENTIFIER ::= { system 4 }

-- dt 55203.1.4.1 integer /system/cpu/dataplane-utilization
cpuTotalUtilisation OBJECT-TYPE
    SYNTAX	Integer32
    MAX-ACCESS	not-accessible
    STATUS	current
    DESCRIPTION
	"Total CPU utilisation in percent"
    ::= { cpu 1 }

-- dt 55203.1.4.2 integer /system/cpu/controlplane-utilization
cpuControlplaneUtilisation OBJECT-TYPE
    SYNTAX	Integer32
    MAX-ACCESS	not-accessible
    STATUS	current
    DESCRIPTION
	"Controlplane CPU utilisation in percent"
    ::= { cpu 2 }

-- dt 55203.1.4.3 integer /system/cpu/dataplane-utilization
cpuDataplaneUtilisation OBJECT-TYPE
    SYNTAX	Integer32
    MAX-ACCESS	not-accessible
    STATUS	current
    DESCRIPTION
	"Dataplane CPU utilisation in percent"
    ::= { cpu 3 }

-- dt 55203.1.4.4 integer /system/cpu/count
cpuCount OBJECT-TYPE
    SYNTAX	Integer32
    MAX-ACCESS	not-accessible
    STATUS	current
    DESCRIPTION
	"Number of CPUs"
    ::= { cpu 4 }

cpuTable OBJECT-TYPE
    SYNTAX	SEQUENCE OF cpuEntry
    MAX-ACCESS	not-accessible
    STATUS	current
    DESCRIPTION
	"A table with CPUs information"
    ::= { cpu 5 }

cpuEntry OBJECT-TYPE
    SYNTAX cpuEntry
    MAX-ACCESS	not-accessible
    STATUS	current
    DESCRIPTION
	"Entry containing information related to specific cpu"
    INDEX	{ cpuName }
    ::= { cpuTable 1 }

cpuEntry ::= SEQUENCE {
    cpuName	DisplayString,
    cpuUtilisation	Integer32,
}

-- dt 55203.1.4.5.1.1.[0-64] string /system/cpu/cpus/$/name
cpuName OBJECT-TYPE
    SYNTAX	DisplayString
    MAX-ACCESS	read-only
    STATUS	current
    DESCRIPTION
	"CPU name"
    ::= { cpuEntry 1 }

-- dt 55203.1.4.5.1.2.[0-64] integer /system/cpu/cpus/$/utilization
cpuUtilisation OBJECT-TYPE
    SYNTAX	Integer32
    MAX-ACCESS	read-only
    STATUS	current
    DESCRIPTION
	"CPU utilization in percent"
    ::= { cpuEntry 2 }


trafficManager	OBJECT IDENTIFIER ::= { netxMib 2 }

-- dt 55203.2.1 timeticks /traffic-manager/scan_time
scanTime OBJECT-TYPE
    SYNTAX	TimeTicks
    MAX-ACCESS 	read-only
    STATUS	current
    DESCRIPTION
	"Traffic Manager Scan Sime in seconds"
    ::= { trafficManager 1 }

-- dt 55203.2.2 integer /traffic-manager/UPDATED
lastUpdated OBJECT-TYPE
    SYNTAX	Integer32
    MAX-ACCESS 	read-only
    STATUS	current
    DESCRIPTION
	"Traffic Manager timestamp of last updated time"
    ::= { trafficManager 2 }

-- dt 55203.2.3 integer /traffic-manager/INSTALLED_RECORDS
installedRecords OBJECT-TYPE
    SYNTAX	Integer32
    MAX-ACCESS 	read-only
    STATUS	current
    DESCRIPTION
	"Traffic Manager Installed number of records"
    ::= { trafficManager 3 }

-- dt 55203.2.4 timeticks /traffic-manager/QUERY_EXECUTION_TIME
queryExecutionTime OBJECT-TYPE
    SYNTAX	TimeTicks
    MAX-ACCESS 	read-only
    STATUS	current
    DESCRIPTION
	"Traffic Manager Query execution time"
    ::= { trafficManager 4 }

-- dt 55203.2.5 string /traffic-manager/QUERY_STATUS
queryStatus OBJECT-TYPE
    SYNTAX	DisplayString
    MAX-ACCESS	not-accessible
    STATUS	current
    DESCRIPTION
	"Traffic Manager Query status"
    ::= { trafficManager 5 }

-- dt 55203.2.6 integer /traffic-manager/QUERY_RECORDS
queryReturnedRecords OBJECT-TYPE
    SYNTAX	Integer32
    MAX-ACCESS 	read-only
    STATUS	current
    DESCRIPTION
	"Traffic Manager Number of records returned by query"
    ::= { trafficManager 6 }

END
